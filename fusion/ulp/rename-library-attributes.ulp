#usage "en: <b>Bulk-rename device attributes across the open Electronics library</b> "
       "(e.g. \"Digikey\" -> \"SPN\" on every part). Run this from the <b>Library "
       "editor</b> with your library open. Edit the RENAMES table near the top first.\n\n"
       "Safety: <b>dry run</b> by default - it only PREVIEWS changes and saves a .scr. "
       "Review it, BACK UP the library, then Automate -> Run Script -> that .scr.\n"

// =============================================================================
// EDIT ME: attribute renames. Add a line per pair and bump RENAME_COUNT logic
// is automatic (RENAME_COUNT++). Matching on OLD_NAME is CASE-INSENSITIVE;
// NEW_NAME is written verbatim.
// =============================================================================
string OLD_NAME[];
string NEW_NAME[];
int    RENAME_COUNT = 0;

void initRenames() {
  OLD_NAME[RENAME_COUNT] = "Digikey"; NEW_NAME[RENAME_COUNT] = "SPN"; RENAME_COUNT++;
  // OLD_NAME[RENAME_COUNT] = "MF"; NEW_NAME[RENAME_COUNT] = "Manufacturer"; RENAME_COUNT++;
}

// -----------------------------------------------------------------------------
// Mechanism (verified against the standard set-all-devices-attribute.ulp):
//   D.technologies is a SPACE-SEPARATED STRING (split with strsplit), and
//   attributes are read via the 2-arg loop  D.attributes(A, technologyName).
//   For each match we emit, per device+technology:
//     EDIT '<deviceset>.dev'; PACKAGE '<variant>'; TECHNOLOGY '<tech>';
//     ATTRIBUTE <NEW> '<value>';   ATTRIBUTE <OLD> DELETE;
//   i.e. rename = copy value to the new name, then delete the old name.
//   Library attributes do NOT propagate from schematic/board, so run this in
//   the LIBRARY editor.
// -----------------------------------------------------------------------------

int    PREVIEW_MAX = 12;  // cap preview lines so the dialog doesn't overflow the screen

string scr = "";       // generated script
string report = "";    // human-readable preview (first PREVIEW_MAX matches only)
int    renameCount = 0;
int    deviceTouched = 0;
string seenNames[];    // distinct attribute names seen (discovery aid)
int    seenCount = 0;

int matchIndex(string upperName) {
  for (int i = 0; i < RENAME_COUNT; i++)
    if (upperName == strupr(OLD_NAME[i])) return i;
  return -1;
}

void noteSeen(string name) {
  for (int i = 0; i < seenCount; i++)
    if (seenNames[i] == name) return;
  seenNames[seenCount++] = name;
}

if (!library) {
  dlgMessageBox("Open this ULP from the Library editor (it edits the currently "
                "open library). It does nothing useful in a schematic/board.");
  exit(0);
}

initRenames();
if (RENAME_COUNT == 0) {
  dlgMessageBox("No renames configured. Edit the RENAMES table at the top first.");
  exit(0);
}

library(L) {
  L.devicesets(DS) {
    DS.devices(D) {
      string techs[];
      int nt = strsplit(techs, D.technologies, ' ');
      if (nt == 0) { techs[0] = ""; nt = 1; }  // single unnamed technology
      for (int ti = 0; ti < nt; ti++) {
        string tech = techs[ti];
        string pending = "";
        D.attributes(A, tech) {
          noteSeen(A.name);
          int idx = matchIndex(strupr(A.name));
          if (idx >= 0 && A.value != "") {
            sprintf(pending, "%sATTRIBUTE %s '%s';\nATTRIBUTE %s DELETE;\n",
                    pending, NEW_NAME[idx], A.value, A.name);
            renameCount++;
            if (renameCount <= PREVIEW_MAX)
              sprintf(report, "%s  %s / %s / [%s]  %s -> %s = '%s'\n",
                      report, DS.name, D.name, tech, A.name, NEW_NAME[idx], A.value);
          }
        }
        if (pending != "") {
          deviceTouched++;
          string nav;
          sprintf(nav, "EDIT '%s.dev';\n", DS.name);
          if (D.name != "")            // skip PACKAGE for an unnamed/default variant
            sprintf(nav, "%sPACKAGE '%s';\n", nav, D.name);
          if (tech != "")              // skip TECHNOLOGY for an unnamed technology
            sprintf(nav, "%sTECHNOLOGY '%s';\n", nav, tech);
          sprintf(scr, "%s%s%s\n", scr, nav, pending);
        }
      }
    }
  }
}

if (renameCount == 0) {
  string names = "";
  for (int i = 0; i < seenCount; i++)
    sprintf(names, "%s  %s\n", names, seenNames[i]);
  string msg;
  sprintf(msg, "No attributes matched your RENAMES table.\n\n"
               "Attribute names found in this library (%d):\n%s\n"
               "Edit the OLD_NAME values at the top of this ULP to match one of "
               "these, then re-run.", seenCount, names);
  dlgMessageBox(msg);
  exit(0);
}

string head;
sprintf(head, "# Generated by rename-library-attributes.ulp\n"
              "# Renames %d attribute(s) across %d device/technology block(s).\n"
              "# BACK UP the library, then Automate -> Run Script -> this file.\n\n",
        renameCount, deviceTouched);

string fileName = dlgFileSave("Save attribute-rename script",
                              "rename-attributes.scr",
                              "Script files (*.scr);;All files (*)");
if (fileName != "") {
  output(fileName, "wt") { printf("%s%s", head, scr); }
  string more = "";
  if (renameCount > PREVIEW_MAX)
    sprintf(more, "  ... and %d more (full list in the saved .scr)\n",
            renameCount - PREVIEW_MAX);
  string msg;
  sprintf(msg, "DRY RUN - nothing changed yet.\n\n"
               "Will rename %d attribute(s) across %d block(s). Preview:\n\n%s%s\n"
               "Saved script to:\n%s\n\n"
               "Next: BACK UP the library, then Automate -> Run Script -> that .scr.",
          renameCount, deviceTouched, report, more, fileName);
  dlgMessageBox(msg);
}
