#usage "en: <b>Extract this design's electronic-component BOM</b> (grouped by part, "
       "with quantity + designators per line). Run from the <b>Schematic</b> editor "
       "(best — richest attributes) or the <b>Board</b> editor. Writes a <b>.json</b> "
       "ready to POST to the Stock Manager (<i>/api/fusion/bom</i>) and a sibling "
       "<b>.csv</b> you can paste straight into a board's BOM box in the app. "
       "Read-only; it changes nothing in the design.\n"

// ---------------------------------------------------------------------------
// String helpers
// ---------------------------------------------------------------------------

// JSON-escape a string value (quotes, backslash, control chars).
string jsonEscape(string s) {
  string out = "";
  int n = strlen(s);
  for (int i = 0; i < n; i++) {
    string c = strsub(s, i, 1);
    if      (c == "\"") out += "\\\"";
    else if (c == "\\") out += "\\\\";
    else if (c == "\n") out += "\\n";
    else if (c == "\r") out += "\\r";
    else if (c == "\t") out += "\\t";
    else out += c;
  }
  return out;
}

// Replace commas with spaces. The app's BOM paste box splits each line on ','
// into "MPN, qty, value, package, designators", so any field we emit must not
// contain a comma or it would spill into the next column.
string noComma(string s) {
  string out = "";
  int n = strlen(s);
  for (int i = 0; i < n; i++) {
    string c = strsub(s, i, 1);
    if (c == ",") out += " "; else out += c;
  }
  return out;
}

// Transliterate the handful of non-ASCII symbols that turn up in component
// values into plain ASCII. Fusion's ULP output() writes the OS ANSI code page
// (observed: Latin-1/Windows-1252, so "µ" is the single byte 0xB5). Left as-is,
// that byte gets mis-decoded downstream — read as EUC-KR it pairs with the next
// character into a bogus Hangul (e.g. "µF" -> "킚"), and Excel mangles it too.
// Emitting ASCII makes the file survive any tool. We match Latin-1 single bytes
// plus the UTF-8 and cp949 multi-byte forms, so it works whatever locale wrote
// the file — and needs no non-ASCII in this source.
string toAscii(string s) {
  string out = "";
  int n = strlen(s);
  int i = 0;
  while (i < n) {
    int b0 = s[i] & 0xFF;
    if (b0 < 0x80) { out += strsub(s, i, 1); i += 1; continue; }
    int b1 = (i + 1 < n) ? (s[i + 1] & 0xFF) : 0;
    int b2 = (i + 2 < n) ? (s[i + 2] & 0xFF) : 0;
    // 3-byte UTF-8
    if      (b0 == 0xE2 && b1 == 0x84 && b2 == 0xA6) { out += "ohm"; i += 3; } // Ω U+2126
    // 2-byte UTF-8
    else if (b0 == 0xCE && b1 == 0xA9)               { out += "ohm"; i += 2; } // Ω U+03A9
    else if (b0 == 0xCE && b1 == 0xBC)               { out += "u";   i += 2; } // μ U+03BC
    else if (b0 == 0xC2 && b1 == 0xB5)               { out += "u";   i += 2; } // µ U+00B5
    else if (b0 == 0xC2 && b1 == 0xB1)               { out += "+/-"; i += 2; } // ± U+00B1
    else if (b0 == 0xC2 && b1 == 0xB0)               { out += "deg"; i += 2; } // ° U+00B0
    // 2-byte cp949/EUC-KR (Korean-locale machines)
    else if (b0 == 0xA5 && b1 == 0xD8)               { out += "ohm"; i += 2; } // Ω
    else if (b0 == 0xA7 && b1 == 0xD9)               { out += "ohm"; i += 2; } // Ω (ohm sign)
    else if (b0 == 0xA5 && b1 == 0xEC)               { out += "u";   i += 2; } // µ
    else if (b0 == 0xA1 && b1 == 0xBE)               { out += "+/-"; i += 2; } // ±
    else if (b0 == 0xA1 && b1 == 0xC6)               { out += "deg"; i += 2; } // °
    // 1-byte Latin-1 / Windows-1252 (what Fusion's output() actually writes here)
    else if (b0 == 0xB5)                             { out += "u";   i += 1; } // µ
    else if (b0 == 0xB1)                             { out += "+/-"; i += 1; } // ±
    else if (b0 == 0xB0)                             { out += "deg"; i += 1; } // °
    // any other non-ASCII byte: drop it (keeps the field pure ASCII)
    else i += 1;
  }
  return out;
}

// Index of the last path separator ('/' or '\'), or -1 if none.
int lastSep(string s) {
  int a = strrchr(s, '/');
  int b = strrchr(s, '\\');
  return a > b ? a : b;
}

// File name without its directory or extension (used as the board name).
string baseName(string path) {
  string f = strsub(path, lastSep(path) + 1);
  int dot = strrchr(f, '.');
  if (dot > 0) f = strsub(f, 0, dot);
  return f;
}

// Same path with its extension swapped (e.g. board-bom.json -> board-bom.csv).
string swapExt(string name, string ext) {
  int dot = strrchr(name, '.');
  if (dot > lastSep(name)) return strsub(name, 0, dot) + ext;
  return name + ext;
}

// ---------------------------------------------------------------------------
// Grouped BOM accumulation
//   Identical parts collapse into one line. The key is the MPN when present,
//   otherwise value + package + deviceset (so a 10k 0603 resistor and a 10k
//   0805 resistor stay separate, but every 10k 0603 merges).
// ---------------------------------------------------------------------------

string bomKey[];    // dedupe key
string bomMpn[];    // manufacturer part number ("" if unknown)
string bomValue[];  // part value
string bomPkg[];    // package / footprint name
string bomDes[];    // comma-joined designators (refdes), capped near the API limit
int    bomQty[];    // quantity per board
int    bomN = 0;    // number of distinct line items

int    totalParts = 0;    // populated components counted
int    skippedNoPkg = 0;  // parts with no physical package (supply/GND symbols)
int    skippedFrame = 0;  // drawing title-block frames (not real components)

// Title-block frames slip past the package check (they carry a placeholder
// package like CREATIVE_COMMONS), so drop them explicitly. Matches the standard
// frame devicesets (FRAME-*) and the placeholder package name.
int isFrame(string dsName, string pkgName) {
  return (strsub(strupr(dsName), 0, 5) == "FRAME" ||
          strupr(pkgName) == "CREATIVE_COMMONS");
}

void addPart(string mpn, string value, string pkg, string ds, string refdes) {
  totalParts++;
  mpn   = toAscii(mpn);     // MPNs are ASCII, but some libraries dump a value/
  value = toAscii(value);   // description in here — clean it so it can't corrupt.
  pkg   = toAscii(pkg);     // e.g. "4.7kΩ" -> "4.7kohm", "4.7µF" -> "4.7uF"

  string key;
  if (mpn != "") key = "M\t" + mpn;
  else           key = "V\t" + value + "\t" + pkg + "\t" + ds;

  int idx = -1;
  for (int i = 0; i < bomN; i++) {
    if (bomKey[i] == key) { idx = i; break; }
  }

  if (idx < 0) {
    bomKey[bomN]   = key;
    bomMpn[bomN]   = mpn;
    bomValue[bomN] = value;
    bomPkg[bomN]   = pkg;
    bomDes[bomN]   = refdes;
    bomQty[bomN]   = 1;
    bomN++;
  } else {
    bomQty[idx]++;
    // Keep the joined designators under the app's 256-char field cap; the
    // quantity stays exact even when the refdes list is truncated.
    if (strlen(bomDes[idx]) < 240) bomDes[idx] += "," + refdes;
  }
}

// ---------------------------------------------------------------------------
// MPN extraction. The attribute that holds the manufacturer part number varies
// by library, so match a list of common names (case-insensitive).
// ---------------------------------------------------------------------------

int isMpnAttr(string nameUpper) {
  return (nameUpper == "MPN" ||
          nameUpper == "MANUFACTURER_PART_NUMBER" ||
          nameUpper == "MANUFACTURERPARTNUMBER" ||
          nameUpper == "MFR_PN" ||
          nameUpper == "MF_PARTNUMBER" ||
          nameUpper == "PART_NUMBER");
}

string mpnOfPart(UL_PART P) {
  string mpn = "";
  P.attributes(A) {
    if (A.value != "" && isMpnAttr(strupr(A.name))) mpn = A.value;
  }
  return mpn;
}

string mpnOfElement(UL_ELEMENT E) {
  string mpn = "";
  E.attributes(A) {
    if (A.value != "" && isMpnAttr(strupr(A.name))) mpn = A.value;
  }
  return mpn;
}

// ---------------------------------------------------------------------------
// Read the active design (schematic preferred, board as a fallback)
// ---------------------------------------------------------------------------

string boardName = "design";

if (schematic) {
  schematic(S) {
    boardName = baseName(S.name);
    S.parts(P) {
      if (P.populate) {                          // skip "do not populate" parts
        // Guard the object itself: supply/frame symbols have no package, and
        // their P.device.package is an *uninitialized* object — reading .name
        // on it throws "Reference to uninitialized object variable".
        if (!P.device.package)
          skippedNoPkg++;
        else if (isFrame(P.deviceset.name, P.device.package.name))
          skippedFrame++;
        else
          addPart(mpnOfPart(P), P.value, P.device.package.name, P.deviceset.name, P.name);
      }
    }
  }
}
else if (board) {
  board(B) {
    boardName = baseName(B.name);
    B.elements(E) {
      if (E.populate) {                          // skip "do not populate" parts
        if (!E.package)                          // physical elements normally have one
          skippedNoPkg++;
        else if (isFrame(E.name, E.package.name))
          skippedFrame++;
        else
          addPart(mpnOfElement(E), E.value, E.package.name, "", E.name);
      }
    }
  }
}
else {
  dlgMessageBox("Open this from a Schematic or Board editor — it reads the active design.");
  exit(0);
}

if (bomN == 0) {
  dlgMessageBox("No populated components with a package were found in this design.");
  exit(0);
}

// ---------------------------------------------------------------------------
// Write the outputs
// ---------------------------------------------------------------------------

string jsonFile = dlgFileSave("Save BOM (JSON for the Stock Manager API)",
                              boardName + "-bom.json",
                              "JSON files (*.json);;All files (*)");
if (jsonFile == "") exit(0);
string csvFile = swapExt(jsonFile, ".csv");

int linesWithMpn = 0;
for (int i = 0; i < bomN; i++) if (bomMpn[i] != "") linesWithMpn++;

// JSON — matches the app's /api/fusion/bom payload (fusionImportSchema) exactly.
output(jsonFile, "wt") {
  printf("{\n");
  printf("  \"board\": { \"name\": \"%s\" },\n", jsonEscape(boardName));
  printf("  \"lines\": [\n");
  for (int i = 0; i < bomN; i++) {
    printf("    {");
    if (bomMpn[i] != "") printf("\"partMpn\": \"%s\", ", jsonEscape(bomMpn[i]));
    else                 printf("\"partMpn\": null, ");
    printf("\"value\": \"%s\", \"package\": \"%s\", \"designators\": \"%s\", \"qtyPerBoard\": %d}",
           jsonEscape(bomValue[i]), jsonEscape(bomPkg[i]), jsonEscape(bomDes[i]), bomQty[i]);
    if (i < bomN - 1) printf(",");
    printf("\n");
  }
  printf("  ]\n}\n");
}

// CSV — one line per part: "MPN, qty, value, package, designators".
// Designators are space-joined (not comma) so the paste box keeps them in a
// single field. No header row: the paste parser treats every line as data.
output(csvFile, "wt") {
  for (int i = 0; i < bomN; i++) {
    printf("%s, %d, %s, %s, %s\n",
           bomMpn[i], bomQty[i],
           noComma(bomValue[i]), noComma(bomPkg[i]), noComma(bomDes[i]));
  }
}

string msg, tmp;
sprintf(msg, "BOM extracted from \"%s\".\n\n", boardName);
sprintf(tmp, "Components (populated): %d\nLine items (grouped): %d\nWith MPN: %d\n",
        totalParts, bomN, linesWithMpn);
msg += tmp;
if (skippedNoPkg > 0) {
  sprintf(tmp, "Skipped (no package — supply/GND symbols): %d\n", skippedNoPkg);
  msg += tmp;
}
if (skippedFrame > 0) {
  sprintf(tmp, "Skipped (drawing frames): %d\n", skippedFrame);
  msg += tmp;
}
msg += "\nSaved:\n  " + jsonFile + "\n  " + csvFile +
       "\n\nNext: POST the JSON to the app's /api/fusion/bom endpoint, or open a "
       "board in the app and paste the CSV into its BOM box.";
dlgMessageBox(msg);
